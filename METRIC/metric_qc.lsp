;;; =====================================================================
;;; METRIC_QC.LSP  v2.10   (clean rewrite)
;;;
;;; v2.1: value-rescue pass.  An inch entity stranded by position-greedy
;;;       matching inside a cluster of near-identical callouts is no longer
;;;       a false MISSING -- if its converted value exists in an unmatched
;;;       metric entity anywhere, they are paired.  MISSING now strictly
;;;       means "this converted value appears NOWHERE in the metric drawing".
;;;
;;; PURPOSE
;;;   Verify that an inch drawing was correctly converted to a metric
;;;   drawing by a macro/script.  The two drawings share IDENTICAL
;;;   geometry and coordinates (they overlap exactly) -- only the
;;;   DISPLAYED dimension/text values differ (inch vs mm).
;;;
;;; CORE CONCEPT  (why this version works where value-matching failed)
;;;   * MATCH BY POSITION, VERIFY BY VALUE.
;;;     Because both drawings sit in the same coordinate space, an entity
;;;     is at the SAME XY in both files.  Pair inch<->metric entities by
;;;     location (nearest neighbour, distance ~ 0 for true partners), then
;;;     check  inch_displayed * 25.4  ==  metric_displayed.
;;;   * This catches the real failure modes:
;;;       - dim the macro forgot to convert  -> pairs by position, fails value
;;;       - dim the macro dropped entirely    -> inch dim unmatched = MISSING
;;;       - NTS dims (703 -> 7030 on purpose)  -> ONE balloon, both values
;;;   * No value-based pairing, no DIA/RAD/TOL kind guessing, no dedup
;;;     hacks -- position is unique and reliable.
;;;
;;; READING CORRECTNESS
;;;   * Dimensions inside blocks are read with a full 2D transform matrix
;;;     accumulated through every nesting level, so their positions are
;;;     true WORLD coordinates (old versions read raw block-local coords).
;;;   * Displayed value = text-override number, else Measurement * DimLFac.
;;;
;;; COMMANDS
;;;   METRIC_CHECK / MQC  -- run QC, place pass/fail balloons on metric dwg
;;;   MQC_DIAG            -- text-only dump of matches/missing/extra
;;;   MQC_CLEAR          -- remove QC balloons + layers
;;;   MQC_TEST           -- parser / matcher self test
;;;
;;;   LOAD ONLY THIS FILE (do not also load the old metric_check.lsp).
;;; =====================================================================

(vl-load-com)

;;; -------------------------------------------------------------------
;;; Settings
;;; -------------------------------------------------------------------
(setq *qc-conv*       25.4)   ; inch -> mm
(setq *qc-tol*        0.6)    ; mm.  Rounding to nearest whole mm gives <=0.5mm
                              ; error for any size, so 0.6 covers rounding while
                              ; still catching genuine conversion errors.
;; Value tie-breaker: when two metric entities fall inside the absolute
;; tolerance of one inch entity, multiply the value-CORRECT candidate's score
;; by this factor so it wins.  A same-spot wrong-value dim (distance ~ 0)
;; still wins outright because the bonus is a multiplier, so an un-converted
;; dim is still matched and flagged FAIL.
(setq *qc-valbonus*   0.6)
;; Single ABSOLUTE-distance match tolerance, in drawing units (mm in the
;; metric file).  Replaces the old normalised-spread gate which behaved
;; differently between drawings (an outlier dim could inflate or shrink the
;; spread, changing the effective gate).  Absolute is consistent across every
;; drawing.  Set to 50 mm: any real partner that ended up that far apart
;; during conversion (text repositioning, leader nudging) is still well
;; within "on top of each other" when both drawings are overlaid.
(setq *qc-exact-tol*  50.0)
;; Force-pair gate: effectively infinite.  The FINAL matching phase uses this
;; so that EVERY remaining inch entity is paired with a remaining metric entity
;; -- no gate, nothing left behind.  This enforces the hard invariant that an
;; in-place inch->metric conversion is 1:1 (it never adds or removes a dim), so
;; EXTRA / MISSING are impossible.  After this phase, a leftover can only exist
;; when the two drawings yielded a DIFFERENT COUNT of dims/texts -- i.e. a
;; genuine collection discrepancy, not a matching failure.  Pairing is ranked
;; value-correct-first (via the value tie-breaker) then nearest position, so an
;; un-converted dim (same spot, wrong value) is still paired and flagged FAIL.
(setq *qc-force-gate* 1.0e12)
(setq *qc-max-depth*  8)      ; block nesting recursion limit
(setq *qc-ignore-blocks*
  "C,D,KF,CAP,BOM,BOM1,REVD,REVSYMB,REVC,REVTRI,REVCIRCLE,REVCLOUD,REVISION,TITLEBLOCK,BORDER,TB,TITLE,FRAME,LOGO")
;; Words (>= 2 letters, upper-case) that legitimately appear inside a dimension
;; callout.  They are NOT counted as "prose" when deciding whether a text is a
;; note vs a dimension.  Anything else of >= 2 letters is treated as prose.
(setq *qc-dim-keywords*
  (list "THRU" "DIA" "DIAM" "DIAMETER" "RAD" "RADIUS" "REF" "TYP" "TYPICAL"
        "MAX" "MIN" "NOM" "NOMINAL" "BSC" "BASIC" "NTS" "PLCS" "PLC" "PLACES"
        "PLACE" "DEEP" "DP" "CBORE" "CSK" "CSINK" "COUNTERBORE" "COUNTERSINK"
        "SPOTFACE" "SFACE" "SF" "FLAT" "STRAIGHT" "UNDERCUT" "FACE" "BORE"
        "BACKFACE" "DEG" "WIDE" "WIDTH" "FULL" "BOTH" "SIDE" "SIDES" "EACH"
        "FAR" "NEAR" "GROOVE" "CHAMFER" "KEYWAY" "SLOT" "DRILL" "REAM" "TAP"
        "MM"))
(setq *qc-active-inch-doc* nil)
(setq *qc-active-inch-dbx* nil)

;;; accumulators (reset per drawing)
(setq *qc-dims*    nil)
(setq *qc-texts*   nil)
(setq *qc-blocks*  nil)
(setq *qc-doc-lfac* 1.0)   ; document DIMLFAC of the drawing currently being read
;;; collection diagnostics (reset per drawing) -- tells us WHERE dims are found
(setq *qc-space-kind* 'MS) ; 'MS while reading modelspace, 'LAY while reading layouts
(setq *qc-dbg-msdim*  0)   ; dims found directly in modelspace
(setq *qc-dbg-blkdim* 0)   ; dims found nested inside block references
(setq *qc-dbg-laydim* 0)   ; dims found in paper-space layouts
(setq *qc-dbg-skipdim* 0)  ; linear dims seen but DROPPED (no value or no position)

;;; -------------------------------------------------------------------
;;; Tiny helpers
;;; -------------------------------------------------------------------
(defun qc:num (x dflt)
  (if (and (not (vl-catch-all-error-p x)) (numberp x)) x dflt)
)
(defun qc:xy-p (p)
  (and (listp p) (>= (length p) 2) (numberp (car p)) (numberp (cadr p)))
)
(defun qc:dist (a b / dx dy)
  (setq dx (- (car a) (car b)) dy (- (cadr a) (cadr b)))
  (sqrt (+ (* dx dx) (* dy dy)))
)
(defun qc:member (n lst / f x)
  (setq f nil)
  (foreach x lst (if (= x n) (setq f T)))
  f
)
(defun qc:is-digit (c)
  (and c (= (type c) 'STR) (= (strlen c) 1) (>= (ascii c) 48) (<= (ascii c) 57))
)
(defun qc:rtrim0 (s)
  (while (and (> (strlen s) 1) (= (substr s (strlen s) 1) "0") (vl-string-search "." s))
    (setq s (substr s 1 (1- (strlen s)))))
  (if (and (> (strlen s) 1) (= (substr s (strlen s) 1) "."))
    (setq s (substr s 1 (1- (strlen s)))))
  s
)
(defun qc:fmt (v)
  (if (numberp v) (qc:rtrim0 (rtos v 2 4)) "?")
)
(defun qc:str-upper (s)
  (if (= (type s) 'STR) (strcase s) "")
)

;;; -------------------------------------------------------------------
;;; 2D affine transform matrix  (a b c d e f):
;;;   wx = a*x + c*y + e
;;;   wy = b*x + d*y + f
;;; -------------------------------------------------------------------
(defun qc:m-identity () (list 1.0 0.0 0.0 1.0 0.0 0.0))
(defun qc:m-apply (m p / x y)
  (setq x (car p) y (cadr p))
  (list (+ (* (nth 0 m) x) (* (nth 2 m) y) (nth 4 m))
        (+ (* (nth 1 m) x) (* (nth 3 m) y) (nth 5 m)))
)
;; compose: result applies L first, then M  (M . L)
(defun qc:m-compose (m l)
  (list
    (+ (* (nth 0 m) (nth 0 l)) (* (nth 2 m) (nth 1 l)))
    (+ (* (nth 1 m) (nth 0 l)) (* (nth 3 m) (nth 1 l)))
    (+ (* (nth 0 m) (nth 2 l)) (* (nth 2 m) (nth 3 l)))
    (+ (* (nth 1 m) (nth 2 l)) (* (nth 3 m) (nth 3 l)))
    (+ (* (nth 0 m) (nth 4 l)) (* (nth 2 m) (nth 5 l)) (nth 4 m))
    (+ (* (nth 1 m) (nth 4 l)) (* (nth 3 m) (nth 5 l)) (nth 5 m)))
)
(defun qc:m-from-insert (ins sx sy rot / c s)
  (setq c (cos rot) s (sin rot))
  (list (* sx c) (* sx s) (* (- sy) s) (* sy c) (car ins) (cadr ins))
)

;;; -------------------------------------------------------------------
;;; Safe geometry getters
;;; -------------------------------------------------------------------
(defun qc:safearray-xy (v / r)
  (setq r (vl-catch-all-apply 'vlax-safearray->list (list (vlax-variant-value v))))
  (if (and (not (vl-catch-all-error-p r)) (listp r) (>= (length r) 2)
           (numberp (car r)) (numberp (cadr r)))
    (list (car r) (cadr r))
    nil)
)
(defun qc:obj-insertion (obj / r)
  (setq r (vl-catch-all-apply 'vla-get-InsertionPoint (list obj)))
  (if (vl-catch-all-error-p r) nil (qc:safearray-xy r))
)
;; Entity handle -- a string that is PRESERVED when the conversion script edits
;; the drawing in place (SaveAs keeps handles).  The inch dim and its converted
;; metric dim are the SAME entity, hence the SAME handle.  This is the exact
;; 1:1 key that makes EXTRA/MISSING impossible for in-place conversions.
(defun qc:obj-handle (obj / r)
  (setq r (vl-catch-all-apply 'vla-get-Handle (list obj)))
  (if (and (not (vl-catch-all-error-p r)) (= (type r) 'STR) (> (strlen r) 0))
    (strcase r)
    nil)
)
(defun qc:blockref-matrix (br / insR ins)
  (setq insR (vl-catch-all-apply 'vla-get-InsertionPoint (list br)))
  (if (vl-catch-all-error-p insR)
    nil
    (progn
      (setq ins (qc:safearray-xy insR))
      (if (not ins)
        nil
        (qc:m-from-insert ins
          (qc:num (vl-catch-all-apply 'vla-get-XScaleFactor (list br)) 1.0)
          (qc:num (vl-catch-all-apply 'vla-get-YScaleFactor (list br)) 1.0)
          (qc:num (vl-catch-all-apply 'vla-get-Rotation     (list br)) 0.0)))))
)

;;; -------------------------------------------------------------------
;;; MTEXT strip (handles all escape sequences)
;;; -------------------------------------------------------------------
(defun qc:strip-mtext (s / res i len c nc depth skipSemi sc)
  (setq res "" len (strlen s) i 1 depth 0 skipSemi nil)
  (while (<= i len)
    (setq c (substr s i 1))
    (cond
      ((= c "{")
       (setq depth (1+ depth))
       (if (and (< i len) (= (substr s (1+ i) 1) "\\")) (setq skipSemi T)))
      ((= c "}")
       (if (> depth 0) (setq depth (- depth 1)))
       (setq skipSemi nil))
      ((and skipSemi (not (= c ";"))) nil)
      ((and skipSemi (= c ";")) (setq skipSemi nil))
      ((= c "\\")
       (if (<= (1+ i) len)
         (progn
           (setq nc (strcase (substr s (1+ i) 1)))
           (cond
             ((wcmatch nc "P,N,~")
              (setq res (strcat res " ") i (1+ i)))
             ((= nc "S")
              (setq sc (+ i 2))
              (while (and (<= sc len) (/= (substr s sc 1) ";")) (setq sc (1+ sc)))
              (setq res (strcat res " ") i sc))
             ((wcmatch nc "F,H,A,C,W,Q,T")
              (setq sc (+ i 2))
              (while (and (<= sc len) (/= (substr s sc 1) ";")) (setq sc (1+ sc)))
              (setq i sc))
             ((and (= nc "U") (<= (+ i 2) len) (= (substr s (+ i 2) 1) "+"))
              (setq res (strcat res " ") i (+ i 6)))
             ((wcmatch nc "L,O,K,X")
              (setq i (1+ i)))
             ((= nc "\\")
              (setq res (strcat res "\\") i (1+ i)))
             (T nil)))))
      ((and (= c "%") (<= (1+ i) len) (= (substr s (1+ i) 1) "%"))
       (setq i (+ i 2)))
      (T (setq res (strcat res c))))
    (setq i (1+ i)))
  res
)
(defun qc:normalize-cc (s / u dia pm)
  (setq u (qc:str-upper s))
  ;; MText / DXF unicode escapes (pure-ASCII source -- safe to edit/save).
  (while (vl-string-search "\\U+00D8" u) (setq u (vl-string-subst "%%C" "\\U+00D8" u)))
  (while (vl-string-search "\\U+2205" u) (setq u (vl-string-subst "%%C" "\\U+2205" u)))
  (while (vl-string-search "\\U+2300" u) (setq u (vl-string-subst "%%C" "\\U+2300" u)))
  (while (vl-string-search "\\U+00B1" u) (setq u (vl-string-subst "+/-" "\\U+00B1" u)))
  ;; Raw UTF-8 byte sequences, built with chr so the SOURCE stays pure ASCII
  ;; (so editor/PowerShell encoding round-trips can never corrupt a literal
  ;; symbol again): diameter U+00D8 = bytes 195 152; plus-minus U+00B1 = 194 177.
  (setq dia (strcat (chr 195) (chr 152))
        pm  (strcat (chr 194) (chr 177)))
  (while (vl-string-search dia u) (setq u (vl-string-subst "%%C" dia u)))
  (while (vl-string-search pm  u) (setq u (vl-string-subst "+/-" pm  u)))
  u
)
(defun qc:contains-any (s patterns / hit p u)
  (setq hit nil u (qc:normalize-cc s))
  (foreach p patterns (if (vl-string-search p u) (setq hit T)))
  hit
)

;;; -------------------------------------------------------------------
;;; Numeric extraction
;;; -------------------------------------------------------------------
(defun qc:extract-number-pairs (str / result i len c token hadDot hadDigitAfterDot stopToken sign nextc)
  (setq result nil len (strlen str) i 1)
  (while (<= i len)
    (setq c (substr str i 1) sign "")
    (if (and (or (= c "+") (= c "-")) (< i len)
             (or (qc:is-digit (substr str (1+ i) 1)) (= (substr str (1+ i) 1) ".")))
      (progn
        (setq nextc (substr str (1+ i) 1))
        (if (or (= i 1) (not (qc:is-digit (substr str (1- i) 1))))
          (progn (setq sign c i (1+ i) c nextc)))))
    (cond
      ((qc:is-digit c)
       (setq token (strcat sign c) hadDot nil hadDigitAfterDot nil stopToken nil i (1+ i))
       (while (and (<= i len) (not stopToken)
                   (or (qc:is-digit (substr str i 1)) (= (substr str i 1) ".")))
         (setq c (substr str i 1))
         (cond
           ((qc:is-digit c)
            (setq token (strcat token c))
            (if hadDot (setq hadDigitAfterDot T)))
           ((= c ".")
            (if hadDot
              (setq stopToken T)
              (progn (setq token (strcat token c) hadDot T)))))
         (if (not stopToken) (setq i (1+ i))))
       (if (not (and hadDot (not hadDigitAfterDot)))
         (setq result (cons (list (atof token) hadDot token) result)))
       (setq i (1- i)))
      ((and (= c ".") (< i len) (qc:is-digit (substr str (1+ i) 1)))
       (setq token (strcat sign "0.") i (+ i 1))
       (while (and (<= i len) (qc:is-digit (substr str i 1)))
         (setq token (strcat token (substr str i 1)) i (1+ i)))
       (setq result (cons (list (atof token) T token) result))
       (setq i (1- i))))
    (setq i (1+ i)))
  (reverse result)
)
(defun qc:first-number (str / pairs p decimalVal intVal)
  (setq pairs (qc:extract-number-pairs str) decimalVal nil intVal nil)
  (foreach p pairs
    (if (and (listp p) (numberp (car p)))
      (cond
        ((and (cadr p) (not decimalVal)) (setq decimalVal (car p)))
        ((and (not (cadr p)) (not intVal)) (setq intVal (car p))))))
  (cond ((numberp decimalVal) decimalVal) ((numberp intVal) intVal) (T nil))
)
;; --- Note / prose rejection -------------------------------------------------
;; A dimension callout is short and number-dominated (R0.06, %%C.771 THRU,
;; 288.925, (3.18)).  A NOTE is prose: a numbered bullet and/or a sentence of
;; words ("1. MATERIAL: AISI 4340", "BREAK ALL SHARP EDGES 0.25/0.51").  Numbers
;; inside notes (material grades, spec numbers, edge-break values) are NOT
;; dimensions and must never be pulled out.

;; Count alphabetic words (>= 2 letters) that are NOT dimension keywords.
;; Two or more such words => the text reads like prose, not a dimension callout.
(defun qc:prose-word-count (s / u i len c word words n w)
  (setq u (strcase s) i 1 len (strlen u) word "" words nil)
  (while (<= i len)
    (setq c (substr u i 1))
    (if (and (>= (ascii c) 65) (<= (ascii c) 90))
      (setq word (strcat word c))
      (progn
        (if (> (strlen word) 0) (setq words (cons word words)))
        (setq word "")))
    (setq i (1+ i)))
  (if (> (strlen word) 0) (setq words (cons word words)))
  (setq n 0)
  (foreach w words
    (if (and (>= (strlen w) 2) (not (member w *qc-dim-keywords*)))
      (setq n (1+ n))))
  n
)
;; Text begins with a list bullet: 1-2 leading digits, then "." or ")", then a
;; space or end-of-string.  Crucially the char AFTER the punctuation must NOT be
;; a digit -- otherwise a real decimal like "12.421" or "0.625" would be
;; mistaken for the bullet "12." and wrongly thrown away.
(defun qc:note-bullet-p (s / tt n p after)
  (setq tt (vl-string-trim " \t\r\n" s))
  (if (and (> (strlen tt) 1) (qc:is-digit (substr tt 1 1)))
    (progn
      (setq n 1)
      (if (and (>= (strlen tt) 2) (qc:is-digit (substr tt 2 1))) (setq n 2))
      (if (>= (strlen tt) (+ n 1))
        (progn
          (setq p (substr tt (+ n 1) 1))
          (if (or (= p ".") (= p ")"))
            (if (>= (strlen tt) (+ n 2))
              (progn (setq after (substr tt (+ n 2) 1))
                     (or (= after " ") (= after "\t")))
              T)                                  ; punctuation at end -> bullet
            nil))
        nil))
    nil)
)
;; Thread-callout detection.
;; Metric thread callouts (M20x212.7P, M12x1.75 THRU, M6x1) start with the
;; capital letter M directly followed by a digit.  The pitch and length values
;; inside these strings (e.g. 212.7 in "M20x212.7P T 1.03") look like dimensions
;; but are NOT -- they don't convert by 25.4 and should never be extracted.
;; Inch thread callouts that use "NF"/"NC"/"UNC"/"UNF"/"NPT" are already caught
;; by bad-word-p; this covers the M-prefix metric variety.
(defun qc:thread-callout-p (s / tt)
  (setq tt (vl-string-trim " \t\r\n()" s))
  (and (>= (strlen tt) 2)
       (= (substr (strcase tt) 1 1) "M")
       (qc:is-digit (substr tt 2 1)))
)
;; Extract the dimensional numbers worth checking from a text string.
;;   * Reject thread callouts (M20x...), numbered bullets, prose outright.
;;   * From a real callout, take only DECIMAL values -- integers are counts,
;;     angles (12 X 30deg) and bullets, none of which convert by 25.4.
;;   Recognises: R0.06  (R6.35)  R12.7  %%C.771  288.925  (3.18)  0.625 THRU
;;   Rejects:    M20x212.7P T 1.03   1. MATERIAL AISI 4340   BREAK EDGES 0.25
(defun qc:dim-numbers (str / raw res pairs p val isdec)
  (setq raw (qc:strip-mtext str))
  (if (or (qc:thread-callout-p raw)
          (qc:note-bullet-p raw)
          (>= (qc:prose-word-count raw) 2))
    nil
    (progn
      (setq pairs (qc:extract-number-pairs raw) res nil)
      (foreach p pairs
        (setq val (car p) isdec (cadr p))
        (if (and isdec (numberp val) (> (abs val) 0.0) (< (abs val) 1.0e6))
          (setq res (cons val res))))
      (reverse res)))
)

;;; -------------------------------------------------------------------
;;; Dimension value + position
;;; -------------------------------------------------------------------
(defun qc:linear-dim-p (oname)
  ;; Keep linear / aligned / rotated / radial / diametric (all convert by 25.4).
  ;; Exclude angular (degrees) and ordinate (coordinate value).
  (and (wcmatch oname "*Dimension*")
       (not (wcmatch oname "*Angular*"))
       (not (wcmatch oname "*Ordinate*")))
)
;; Document DIMLFAC (linear scale factor) of a drawing.  A metric drawing
;; converted from inch geometry typically carries DIMLFAC = 25.4 so its dims
;; DISPLAY mm while the underlying geometry stays in inches.
(defun qc:doc-dimlfac (doc / r)
  (setq r (vl-catch-all-apply 'vla-getvariable (list doc "DIMLFAC")))
  (if (and (not (vl-catch-all-error-p r)) (numberp r)
           (>= (abs r) 0.001) (<= (abs r) 1000.0))
    r
    1.0)
)
;; Effective DIMLFAC for one dimension.  Prefer the object's own DimLFac
;; (covers per-dim overrides, including a legitimate 1.0 for mm-geometry dims).
;; ONLY when that read fails do we fall back to the document DIMLFAC -- this is
;; the fix for dims whose object property can't be fetched via COM/ObjectDBX,
;; which were being read at the raw inch value (e.g. "exp 181.102 got 7.13").
;; Read the dimension's OWN DimLFac so we reconstruct the value it actually
;; DISPLAYS.  We deliberately do NOT fall back to the document DIMLFAC: if the
;; conversion script left a dim unconverted (still showing the inch value), we
;; WANT it to read that inch value and FAIL the check, so the user can fix it.
(defun qc:dimlfac (obj / r)
  (setq r (vl-catch-all-apply 'vlax-get-property (list obj "DimLFac")))
  (if (and (not (vl-catch-all-error-p r)) (numberp r)
           (>= (abs r) 0.001) (<= (abs r) 1000.0))
    r
    1.0)
)
(defun qc:dim-override (obj / tr txt s v)
  (setq tr (vl-catch-all-apply 'vla-get-TextOverride (list obj)))
  (if (vl-catch-all-error-p tr)
    nil
    (progn
      (setq txt tr)
      (if (or (not txt) (= txt "") (vl-string-search "<>" txt))
        nil
        (progn
          (setq s (qc:strip-mtext txt) v (qc:first-number s))
          (if (numberp v) v nil)))))
)
(defun qc:dim-value (obj / ov mr m lf)
  (setq ov (qc:dim-override obj))
  (if (numberp ov)
    ov
    (progn
      (setq mr (vl-catch-all-apply 'vla-get-Measurement (list obj)))
      (if (and (not (vl-catch-all-error-p mr)) (numberp mr))
        (progn
          (setq m (abs mr) lf (qc:dimlfac obj))
          (if (and (> (abs lf) 1e-9) (not (equal lf 1.0 1e-6))) (setq m (* m lf)))
          (if (> m 0.0) m nil))
        nil)))
)
(defun qc:dim-localpos (obj / a b p1 p2 tp)
  (setq a (vl-catch-all-apply 'vla-get-ExtLine1Point (list obj))
        b (vl-catch-all-apply 'vla-get-ExtLine2Point (list obj)))
  (if (and (not (vl-catch-all-error-p a)) (not (vl-catch-all-error-p b)))
    (setq p1 (qc:safearray-xy a) p2 (qc:safearray-xy b)))
  (if (and p1 p2)
    (list (/ (+ (car p1) (car p2)) 2.0) (/ (+ (cadr p1) (cadr p2)) 2.0))
    (progn
      (setq tp (vl-catch-all-apply 'vla-get-TextPosition (list obj)))
      (if (not (vl-catch-all-error-p tp)) (qc:safearray-xy tp) nil)))
)

;;; -------------------------------------------------------------------
;;; Block-name filters
;;; -------------------------------------------------------------------
(defun qc:raw-name (br / r)
  (setq r (vl-catch-all-apply 'vla-get-Name (list br)))
  (if (and (not (vl-catch-all-error-p r)) (= (type r) 'STR)) r "")
)
(defun qc:eff-name (br / r)
  (setq r (vl-catch-all-apply 'vla-get-EffectiveName (list br)))
  (if (and (not (vl-catch-all-error-p r)) (= (type r) 'STR)) r (qc:raw-name br))
)
;; A block is ignored if EITHER its effective name OR its raw name (trimmed,
;; upper-cased) is in the ignore list.  Checking both is belt-and-braces: some
;; blocks return a usable EffectiveName, others only a Name, and dynamic blocks
;; differ between the two -- this guarantees e.g. a block literally named "D"
;; is skipped no matter which API answers.
(defun qc:ignored-block-p (br / e r)
  (setq e (strcase (vl-string-trim " \t\r\n" (qc:eff-name br)))
        r (strcase (vl-string-trim " \t\r\n" (qc:raw-name br))))
  (or (wcmatch e *qc-ignore-blocks*)
      (wcmatch r *qc-ignore-blocks*))
)

;;; -------------------------------------------------------------------
;;; Recursive collection (world coordinates via transform matrix)
;;;   *qc-dims*  element : (worldpos value)
;;;   *qc-texts* element : (worldpos nums sourcetext)
;;; -------------------------------------------------------------------
;; Dim entry shape:  (worldpos value handle)
(defun qc:add-dim (obj mtx depth / val lp)
  (setq val (qc:dim-value obj) lp (qc:dim-localpos obj))
  (if (and (numberp val) (qc:xy-p lp))
    (progn
      (setq *qc-dims* (cons (list (qc:m-apply mtx lp) val (qc:obj-handle obj)) *qc-dims*))
      (cond ((> depth 0)               (setq *qc-dbg-blkdim* (1+ *qc-dbg-blkdim*)))
            ((eq *qc-space-kind* 'LAY) (setq *qc-dbg-laydim* (1+ *qc-dbg-laydim*)))
            (T                         (setq *qc-dbg-msdim*  (1+ *qc-dbg-msdim*)))))
    ;; linear dim that we could NOT read (no measurement or no ext-line points)
    (setq *qc-dbg-skipdim* (1+ *qc-dbg-skipdim*)))
)
;; Text entry shape:  (worldpos nums sourcetext handle)
(defun qc:add-text-string (txt lp mtx handle / nums)
  (if (and (= (type txt) 'STR) (qc:xy-p lp))
    (progn
      (setq nums (qc:dim-numbers txt))
      (if nums
        (setq *qc-texts* (cons (list (qc:m-apply mtx lp) nums txt handle) *qc-texts*)))))
)
(defun qc:add-text (obj mtx / oname tr txt lp)
  (setq tr (vl-catch-all-apply 'vla-get-TextString (list obj)))
  (if (and (not (vl-catch-all-error-p tr)) (= (type tr) 'STR))
    (progn
      (setq oname (vla-get-ObjectName obj)
            txt   (if (wcmatch oname "*MText*") (qc:strip-mtext tr) tr)
            lp    (qc:obj-insertion obj))
      (qc:add-text-string txt lp mtx (qc:obj-handle obj))))
)
(defun qc:add-mleader (obj mtx / tr lr txt lp)
  (setq tr (vl-catch-all-apply 'vla-get-TextString   (list obj))
        lr (vl-catch-all-apply 'vla-get-TextLocation (list obj)))
  (if (and (not (vl-catch-all-error-p tr)) (= (type tr) 'STR)
           (not (vl-catch-all-error-p lr)))
    (progn
      (setq txt (qc:strip-mtext tr) lp (qc:safearray-xy lr))
      (qc:add-text-string txt lp mtx (qc:obj-handle obj))))
)
(defun qc:add-attributes (br mtx / hr ar al att lp tr txt)
  (setq hr (vl-catch-all-apply 'vla-get-HasAttributes (list br)))
  (if (and (not (vl-catch-all-error-p hr)) hr)
    (progn
      (setq ar (vl-catch-all-apply 'vla-GetAttributes (list br)))
      (if (not (vl-catch-all-error-p ar))
        (progn
          (setq al (vl-catch-all-apply 'vlax-safearray->list (list (vlax-variant-value ar))))
          (if (and (not (vl-catch-all-error-p al)) (listp al))
            (foreach att al
              (setq tr (vl-catch-all-apply 'vla-get-TextString (list att)))
              (if (and (not (vl-catch-all-error-p tr)) (= (type tr) 'STR))
                (progn
                  (setq lp (qc:obj-insertion att))
                  (qc:add-text-string tr lp mtx (qc:obj-handle att)))))))))) ; attrib pos already world; mtx=identity at top
)
(defun qc:descend-blockref (br mtx depth / lmtx cmtx nm def)
  (if (not (qc:ignored-block-p br))
    (progn
      (qc:add-attributes br mtx)
      (if (< depth *qc-max-depth*)
        (progn
          (setq lmtx (qc:blockref-matrix br))
          (if lmtx
            (progn
              (setq cmtx (qc:m-compose mtx lmtx)
                    nm   (qc:raw-name br))
              (if (and nm (> (strlen nm) 0))
                (progn
                  (setq def (vl-catch-all-apply 'vla-Item (list *qc-blocks* nm)))
                  (if (not (vl-catch-all-error-p def))
                    (qc:collect-space def cmtx (1+ depth)))))))))))
)
(defun qc:collect-space (space mtx depth / obj oname lyr)
  (vlax-for obj space
    (setq lyr (vl-catch-all-apply 'vla-get-Layer (list obj)))
    ;; Skip our own QC markers from a previous run (they live on MC_PASS /
    ;; MC_ERRORS).  Without this, "EXTRA 220.726mm" labels get re-read as text.
    (if (and (= (type lyr) 'STR)
             (or (= (strcase lyr) "MC_PASS") (= (strcase lyr) "MC_ERRORS")))
      nil
      (progn
        (setq oname (vla-get-ObjectName obj))
        (cond
          ((qc:linear-dim-p oname)              (qc:add-dim obj mtx depth))
          ((wcmatch oname "AcDbText,AcDbMText") (qc:add-text obj mtx))
          ((= oname "AcDbMLeader")              (qc:add-mleader obj mtx))
          ((= oname "AcDbBlockReference")       (qc:descend-blockref obj mtx depth))))))
)
(defun qc:collect-layouts (doc / layouts layout lname blk)
  (setq layouts (vl-catch-all-apply 'vla-get-Layouts (list doc)))
  (if (not (vl-catch-all-error-p layouts))
    (vlax-for layout layouts
      (setq lname (vl-catch-all-apply 'vla-get-Name (list layout)))
      (if (and (not (vl-catch-all-error-p lname)) (= (type lname) 'STR)
               (not (= (strcase lname) "MODEL")))
        (progn
          (setq *qc-space-kind* 'LAY)
          (setq blk (vl-catch-all-apply 'vla-get-Block (list layout)))
          (if (not (vl-catch-all-error-p blk))
            (qc:collect-space blk (qc:m-identity) 0))))))
)
(defun qc:collect (doc)
  (setq *qc-dims* nil *qc-texts* nil
        *qc-blocks*   (vla-get-Blocks doc)
        *qc-doc-lfac* (qc:doc-dimlfac doc)
        *qc-dbg-msdim* 0 *qc-dbg-blkdim* 0 *qc-dbg-laydim* 0 *qc-dbg-skipdim* 0
        *qc-space-kind* 'MS)
  (qc:collect-space (vla-get-ModelSpace doc) (qc:m-identity) 0)
  (qc:collect-layouts doc)
  (list *qc-dims* *qc-texts*)
)

;;; -------------------------------------------------------------------
;;; Position matching   (raw coordinates -- same space in both drawings)
;;;   element shape: (pos . rest)  ; (car e) is the XY position
;;;   returns: (matched unmatched-inch unmatched-metric)
;;;   matched element: (inchElem metricElem normalized-distance)
;;; -------------------------------------------------------------------
(defun qc:centroid (lst / n sx sy p)
  (setq n 0 sx 0.0 sy 0.0)
  (foreach e lst
    (setq p (car e))
    (if (qc:xy-p p) (setq sx (+ sx (car p)) sy (+ sy (cadr p)) n (1+ n))))
  (if (> n 0) (list (/ sx n) (/ sy n)) nil)
)
(defun qc:spread (lst c / n s p dx dy)
  (setq n 0 s 0.0)
  (foreach e lst
    (setq p (car e))
    (if (qc:xy-p p)
      (setq dx (- (car p) (car c)) dy (- (cadr p) (cadr c))
            s (+ s (* dx dx) (* dy dy)) n (1+ n))))
  (if (> n 0) (sqrt (/ s n)) 0.0)
)
;; Value signature of an entry: dim -> its number; text -> its first number.
(defun qc:entry-vkey (e / v)
  (setq v (cadr e))
  (cond ((numberp v) v)
        ((and (listp v) v (numberp (car v))) (car v))
        (T nil))
)
;; Collapse COINCIDENT DUPLICATES: entries at essentially the same position
;; AND the same value are one requirement, not two (common from copy-paste,
;; or a block + overlapping text).  posTol is a tiny fraction of drawing
;; spread, so two DISTINCT holes/callouts (always meaningfully apart) are
;; never merged -- only literal overlaps.  This stops a duplicated inch
;; callout from producing a phantom MISSING when metric carries it once.
(defun qc:dedup-coincident (lst / c sp posTol kept e p vk k dup)
  (setq c (qc:centroid lst))
  (if (not c)
    lst
    (progn
      (setq sp (qc:spread lst c))
      (if (<= sp 1e-9) (setq sp 1.0))
      (setq posTol (* sp 1.0e-4) kept nil)   ; 0.01% of spread = truly coincident
      (foreach e lst
        (setq p (car e) vk (qc:entry-vkey e) dup nil)
        (foreach k kept
          (if (and (not dup) (qc:xy-p p) (qc:xy-p (car k))
                   (< (qc:dist p (car k)) posTol)
                   vk (qc:entry-vkey k)
                   (equal vk (qc:entry-vkey k) 1e-6))
            (setq dup T)))
        (if (not dup) (setq kept (cons e kept))))
      (reverse kept)))
)
;; EXACT 1:1 match by entity HANDLE -- the primary matcher.
;;   An in-place conversion keeps each entity's handle, so the inch dim and its
;;   metric counterpart share a handle.  Pairing on handle is exact: no gate, no
;;   ambiguity, and -- crucially -- it makes EXTRA / MISSING impossible whenever
;;   handles are preserved (every inch entity has its metric twin and vice versa).
;;   hidx = index of the handle within an entry (dims: 2, texts: 3).
;;   Returns (matched unmatched-inch unmatched-metric); matched = (ie me 0.0).
;;   Entries with no handle (nil) are passed through as unmatched for the
;;   position fallback, so nothing is lost if a converter rebuilt entities.
(defun qc:match-by-handle (inchL metricL hidx
                           / mtable i e h cell matched usedM inchLeft metricLeft)
  (setq mtable nil i 0)
  (foreach e metricL
    (setq h (nth hidx e))
    (if (and h (= (type h) 'STR)) (setq mtable (cons (cons h i) mtable)))
    (setq i (1+ i)))
  (setq matched nil usedM nil inchLeft nil)
  (foreach e inchL
    (setq h    (nth hidx e)
          cell (if (and h (= (type h) 'STR)) (assoc h mtable) nil))
    (if (and cell (not (qc:member (cdr cell) usedM)))
      (setq matched (cons (list e (nth (cdr cell) metricL) 0.0) matched)
            usedM   (cons (cdr cell) usedM))
      (setq inchLeft (cons e inchLeft))))
  (setq metricLeft nil i 0)
  (foreach e metricL
    (if (not (qc:member i usedM)) (setq metricLeft (cons e metricLeft)))
    (setq i (1+ i)))
  (list (reverse matched) (reverse inchLeft) (reverse metricLeft))
)
;; Value-agreement predicates used as a tie-breaker during position matching.
(defun qc:dim-valok (ie me)
  (<= (abs (- (abs (cadr me)) (* (abs (cadr ie)) *qc-conv*))) *qc-tol*)
)
(defun qc:txt-valok (ie me / inums mnums pairs ok q)
  (setq inums (cadr ie) mnums (cadr me))
  (if (and inums mnums (= (length inums) (length mnums)))
    (progn
      (setq pairs (qc:best-pairs inums mnums)
            ok    (and pairs (= (length pairs) (length inums))))
      (if ok
        (progn (foreach q pairs (if (> (cadddr q) *qc-tol*) (setq ok nil))) ok)
        nil))
    nil)
)
;; Position matcher.  valfn (or nil) is a (lambda (ie me) -> T/nil) value check;
;; when it returns T the candidate's position score is reduced by *qc-valbonus*
;; so a same-location, correctly-converted pair is preferred over a coincidental
;; neighbour -- WITHOUT raising the spatial gate (gate still tests raw distance).
(defun qc:match (inchL metricL gate valfn
                 / cm sm cand i j ie me d vok score sorted usedI usedM matched ui um c)
  (setq cm (qc:centroid metricL))
  (if (not cm)
    (list nil inchL metricL)
    (progn
      (setq sm (qc:spread metricL cm))
      (if (<= sm 1e-9) (setq sm 1.0))
      (setq cand nil i 0)
      (foreach ie inchL
        (if (qc:xy-p (car ie))
          (progn
            (setq j 0)
            (foreach me metricL
              (if (qc:xy-p (car me))
                (progn
                  (setq d (/ (qc:dist (car ie) (car me)) sm))
                  (if (< d gate)
                    (progn
                      (setq vok   (if valfn (apply valfn (list ie me)) nil)
                            score (* d (if vok *qc-valbonus* 1.0)))
                      (setq cand (cons (list score i j ie me) cand))))))
              (setq j (1+ j)))))
        (setq i (1+ i)))
      (setq sorted (vl-sort cand '(lambda (a b) (< (car a) (car b))))
            usedI nil usedM nil matched nil)
      (foreach c sorted
        (if (and (not (qc:member (cadr c) usedI)) (not (qc:member (caddr c) usedM)))
          (setq matched (cons (list (nth 3 c) (nth 4 c) (car c)) matched)
                usedI   (cons (cadr c) usedI)
                usedM   (cons (caddr c) usedM))))
      (setq ui nil i 0)
      (foreach ie inchL (if (not (qc:member i usedI)) (setq ui (cons ie ui))) (setq i (1+ i)))
      (setq um nil j 0)
      (foreach me metricL (if (not (qc:member j usedM)) (setq um (cons me um))) (setq j (1+ j)))
      (list (reverse matched) (reverse ui) (reverse um))))
)

;;; Absolute-position match -- pairs entries closer than *qc-exact-tol* drawing
;;; units regardless of spread or gate.  This is Phase 2 in the pipeline and
;;; runs BEFORE the normalised-gate match so that two entities literally at the
;;; same spot always pair, even when a small leftover set produces a tiny spread
;;; that makes the normalised gate too tight.
(defun qc:match-exact (inchL metricL tol valfn
                       / cand i j ie me d vok score sorted usedI usedM matched ui um c)
  (setq cand nil i 0)
  (foreach ie inchL
    (if (qc:xy-p (car ie))
      (progn
        (setq j 0)
        (foreach me metricL
          (if (qc:xy-p (car me))
            (progn
              (setq d (qc:dist (car ie) (car me)))
              (if (< d tol)
                (progn
                  ;; Value tie-breaker: when a wrong-value and correct-value
                  ;; metric both fall within the (generous) exact-tol, the
                  ;; correct-value candidate must win.  A same-spot wrong-value
                  ;; dim (d ~ 0) still wins outright because the bonus is a
                  ;; multiplier, so an un-converted dimension is still matched
                  ;; and flagged FAIL.
                  (setq vok   (if valfn (apply valfn (list ie me)) nil)
                        score (* d (if vok *qc-valbonus* 1.0)))
                  (setq cand (cons (list score i j ie me) cand))))))
          (setq j (1+ j)))))
    (setq i (1+ i)))
  (setq sorted (vl-sort cand '(lambda (a b) (< (car a) (car b))))
        usedI nil usedM nil matched nil)
  (foreach c sorted
    (if (and (not (qc:member (cadr c) usedI)) (not (qc:member (caddr c) usedM)))
      (setq matched (cons (list (nth 3 c) (nth 4 c) (car c)) matched)
            usedI   (cons (cadr c) usedI)
            usedM   (cons (caddr c) usedM))))
  (setq ui nil i 0)
  (foreach ie inchL (if (not (qc:member i usedI)) (setq ui (cons ie ui))) (setq i (1+ i)))
  (setq um nil j 0)
  (foreach me metricL (if (not (qc:member j usedM)) (setq um (cons me um))) (setq j (1+ j)))
  (list (reverse matched) (reverse ui) (reverse um))
)

;;; Greedy best pairing of two number lists (for multi-number text strings)
;;; returns list of (inchNum metricNum expected diff)
(defun qc:best-pairs (inums mnums / cand i j iv mv ex df sorted sel ui um c)
  (setq cand nil i 0)
  (foreach iv inums
    (setq j 0)
    (foreach mv mnums
      (if (and (numberp iv) (numberp mv))
        (progn
          (setq ex (* (abs iv) *qc-conv*) df (abs (- (abs mv) ex)))
          (setq cand (cons (list df i j iv mv ex) cand))))
      (setq j (1+ j)))
    (setq i (1+ i)))
  (setq sorted (vl-sort cand '(lambda (a b) (< (car a) (car b)))) sel nil ui nil um nil)
  (foreach c sorted
    (if (and (not (qc:member (cadr c) ui)) (not (qc:member (caddr c) um)))
      (setq sel (cons (list (nth 3 c) (nth 4 c) (nth 5 c) (car c)) sel)
            ui  (cons (cadr c) ui)
            um  (cons (caddr c) um))))
  (reverse sel)
)

;;; Value-rescue pass.
;;;   "MISSING" must mean a converted value appears NOWHERE in the metric
;;;   drawing -- not merely that greedy position-matching stranded an entity
;;;   in a cluster of near-identical callouts (e.g., a 12x hole pattern with
;;;   leader copies).  After position matching, each still-unmatched inch
;;;   entity is paired with the NEAREST still-unmatched metric entity whose
;;;   value converts correctly (valfn = T).  If no metric value matches, it
;;;   stays MISSING -- so a genuinely un-converted dimension is still caught.
;;;   Returns (rescued-pairs still-missing-inch still-extra-metric).
(defun qc:value-rescue (missI missM valfn
                        / pairs stillI stillM usedM ie me j d bestMe bestJ bestD)
  (setq pairs nil stillI nil usedM nil)
  (foreach ie missI
    (setq bestMe nil bestJ nil bestD 1.0e99 j 0)
    (foreach me missM
      (if (and (not (qc:member j usedM)) (apply valfn (list ie me)))
        (progn
          (setq d (if (and (qc:xy-p (car ie)) (qc:xy-p (car me)))
                    (qc:dist (car ie) (car me))
                    0.0))
          (if (< d bestD) (setq bestD d bestMe me bestJ j))))
      (setq j (1+ j)))
    (if bestMe
      (setq pairs (cons (list ie bestMe 0.0) pairs)
            usedM (cons bestJ usedM))
      (setq stillI (cons ie stillI))))
  (setq stillM nil j 0)
  (foreach me missM
    (if (not (qc:member j usedM)) (setq stillM (cons me stillM)))
    (setq j (1+ j)))
  (list (reverse pairs) (reverse stillI) (reverse stillM))
)

;;; -------------------------------------------------------------------
;;; Labels
;;; -------------------------------------------------------------------
(defun qc:lbl-ok () "\\U+2713")
(defun qc:lbl-cmp (iv ex mv)
  (strcat (qc:fmt iv) "\" exp " (qc:fmt ex) " got " (qc:fmt mv) "mm")
)
(defun qc:lbl-miss (iv ex)
  (strcat "MISSING  " (qc:fmt iv) "\" exp " (qc:fmt ex) "mm")
)
(defun qc:lbl-extra (mv)
  (strcat "EXTRA  " (qc:fmt mv) "mm")
)

;;; -------------------------------------------------------------------
;;; ObjectDBX open / close
;;; -------------------------------------------------------------------
(defun qc:create-dbx (acadObj / versions prog dbx)
  (setq versions (list "ObjectDBX.AxDbDocument.25" "ObjectDBX.AxDbDocument.24"
                       "ObjectDBX.AxDbDocument.23" "ObjectDBX.AxDbDocument.22"
                       "ObjectDBX.AxDbDocument.21" "ObjectDBX.AxDbDocument.20"
                       "ObjectDBX.AxDbDocument.19" "ObjectDBX.AxDbDocument.18"
                       "ObjectDBX.AxDbDocument")
        dbx nil)
  (foreach prog versions
    (if (not dbx)
      (progn
        (setq dbx (vl-catch-all-apply 'vla-GetInterfaceObject (list acadObj prog)))
        (if (vl-catch-all-error-p dbx) (setq dbx nil)))))
  dbx
)
(defun qc:open-inch (acadObj inchFile / dbx openRes visibleRes)
  (setq dbx (qc:create-dbx acadObj))
  (if dbx
    (progn
      (setq openRes (vl-catch-all-apply 'vla-open (list dbx inchFile)))
      (if (vl-catch-all-error-p openRes)
        (progn
          (vl-catch-all-apply 'vlax-release-object (list dbx))
          (setq visibleRes (vl-catch-all-apply 'vla-open
                             (list (vla-get-Documents acadObj) inchFile vlax-true)))
          (if (vl-catch-all-error-p visibleRes) nil (list visibleRes nil)))
        (list dbx T)))
    (progn
      (setq visibleRes (vl-catch-all-apply 'vla-open
                         (list (vla-get-Documents acadObj) inchFile vlax-true)))
      (if (vl-catch-all-error-p visibleRes) nil (list visibleRes nil))))
)
(defun qc:close-inch (doc isDbx)
  (if doc
    (if isDbx
      (vl-catch-all-apply 'vlax-release-object (list doc))
      (vl-catch-all-apply 'vla-close (list doc vlax-false))))
)

;;; -------------------------------------------------------------------
;;; Layers / balloons
;;; -------------------------------------------------------------------
(defun qc:balloon-height (/ dtxt dscl sz)
  (setq dtxt (getvar "DIMTXT") dscl (getvar "DIMSCALE")
        sz   (* (max dtxt 0.05) (max dscl 1.0) 0.85))
  (max sz 0.5)
)
(defun qc:ensure-layer (doc lname color / layers layerRes addRes)
  (setq layers   (vla-get-Layers doc)
        layerRes (vl-catch-all-apply 'vla-item (list layers lname)))
  (if (vl-catch-all-error-p layerRes)
    (progn
      (setq addRes (vl-catch-all-apply 'vla-add (list layers lname)))
      (if (not (vl-catch-all-error-p addRes)) (vla-put-Color addRes color)))
    (vla-put-Color layerRes color))
)
(defun qc:delete-layer (lname / doc layers layerRes delRes)
  (setq doc      (vla-get-ActiveDocument (vlax-get-acad-object))
        layers   (vla-get-Layers doc)
        layerRes (vl-catch-all-apply 'vla-item (list layers lname)))
  (if (not (vl-catch-all-error-p layerRes))
    (progn
      (if (= (strcase (getvar "CLAYER")) (strcase lname)) (setvar "CLAYER" "0"))
      (setq delRes (vl-catch-all-apply 'vla-delete (list layerRes)))
      (if (vl-catch-all-error-p delRes)
        (vl-catch-all-apply 'command (list "._-PURGE" "_La" lname "_No")))))
)
(defun qc:clear-layers (/ ss i lname)
  (foreach lname (list "MC_PASS" "MC_ERRORS")
    (setq ss (ssget "X" (list (cons 8 lname))))
    (if ss (progn (setq i 0) (repeat (sslength ss) (entdel (ssname ss i)) (setq i (1+ i)))))
    (qc:delete-layer lname))
)
;; Place a QC marker at dimPos.
;;   PASS  -> small green checkmark right at the dimension. No arrow needed.
;;   FAIL  -> error label offset from the dimension + a leader LINE pointing
;;            from the label back to the exact dimension position so the user
;;            can always locate which entity is being flagged, even when dims
;;            are dense or overlapping.
(defun qc:place-marker (isPass body dimPos bh
                        / dx dy ox oy lins llbl lbw led layer color)
  (setq dx (car dimPos) dy (cadr dimPos))
  (if isPass
    ;; --- PASS: tick at dim position ---
    (progn
      (setq lins (list dx (+ dy (* bh 0.6)) 0.0)
            llbl "{\\fArial|b1|i0;\\U+2713}"
            lbw  (* bh 2.0))
      (vl-catch-all-apply 'entmake
        (list (list (cons 0 "MTEXT") (cons 100 "AcDbEntity") (cons 8 "MC_PASS") (cons 62 3)
                    (cons 100 "AcDbMText") (cons 10 lins) (cons 40 bh) (cons 41 lbw)
                    (cons 71 1) (cons 72 1) (cons 1 llbl)))))
    ;; --- FAIL: label offset + leader line pointing to dim ---
    (progn
      ;; Label position: offset up and to the right so it doesn't cover the dim.
      ;; Arrow tip is AT the dim position; tail goes to the label.
      (setq ox (+ dx (* bh 4.0))
            oy (+ dy (* bh 5.0))
            llbl (strcat "{\\fArial|b1|i0;" body "}")
            lbw  (max (* (strlen body) bh 0.52) (* bh 4.0)))
      ;; Leader LINE from label origin down to dim position
      (vl-catch-all-apply 'entmake
        (list (list (cons 0 "LINE") (cons 100 "AcDbEntity") (cons 8 "MC_ERRORS") (cons 62 7)
                    (cons 100 "AcDbLine")
                    (cons 10 (list ox oy 0.0))
                    (cons 11 (list dx dy 0.0)))))
      ;; Small filled arrowhead circle at the dimension tip
      (vl-catch-all-apply 'entmake
        (list (list (cons 0 "CIRCLE") (cons 100 "AcDbEntity") (cons 8 "MC_ERRORS") (cons 62 7)
                    (cons 100 "AcDbCircle")
                    (cons 10 (list dx dy 0.0))
                    (cons 40 (* bh 0.4)))))
      ;; Error label MTEXT at offset position
      (vl-catch-all-apply 'entmake
        (list (list (cons 0 "MTEXT") (cons 100 "AcDbEntity") (cons 8 "MC_ERRORS") (cons 62 7)
                    (cons 100 "AcDbMText") (cons 10 (list ox oy 0.0)) (cons 40 bh) (cons 41 lbw)
                    (cons 71 1) (cons 72 1) (cons 1 llbl))))))
)
(defun qc:dwg-folder (/ p)
  (setq p (getvar "DWGPREFIX"))
  (if (or (not p) (= p "")) (setq p ""))
  p
)

;;; ===================================================================
;;; MAIN  --  METRIC_CHECK / MQC
;;; ===================================================================
(defun c:metric_check
    (/ *error* oldError oldCmd acadObj metricDoc metricDir inchFile inchOpen inchDoc inchIsDbx
       mc-res ic-res metricDims metricTexts inchDims inchTexts metricLfac inchLfac
       dimRes dMatched dMiss dExtra txtRes tMatched tMiss tExtra dResc tResc
       dimMarks txtMarks dimPass dimFail txtPass txtFail
       missDim extraDim missTxt extraTxt
       pr ie me iv mv exp df pass bp inums mnums pairs body bad q qi qm qe qd
       balloonH errIdx m)

  (vl-load-com)
  (setq oldError *error* oldCmd (getvar "CMDECHO")
        *qc-active-inch-doc* nil *qc-active-inch-dbx* nil)

  (defun *error* (msg)
    (if *qc-active-inch-doc* (qc:close-inch *qc-active-inch-doc* *qc-active-inch-dbx*))
    (setq *qc-active-inch-doc* nil *qc-active-inch-dbx* nil)
    (if metricDoc (vl-catch-all-apply 'vla-Activate (list metricDoc)))
    (if oldCmd (setvar "CMDECHO" oldCmd))
    (setq *error* oldError)
    (if (and msg (not (wcmatch (strcase msg) "*CANCEL*,*QUIT*,*BREAK*")))
      (princ (strcat "\nMETRIC_QC error: " msg)))
    (princ))

  (setq acadObj   (vlax-get-acad-object)
        metricDoc (vla-get-ActiveDocument acadObj)
        metricDir (qc:dwg-folder))

  (princ "\n[METRIC_QC v2.10] Reading metric (active) drawing...")
  (setq mc-res      (qc:collect metricDoc)
        metricDims  (car  mc-res)
        metricTexts (cadr mc-res)
        metricLfac  *qc-doc-lfac*)
  (princ (strcat " " (itoa (length metricDims)) " dim(s), "
                     (itoa (length metricTexts)) " text(s)."))

  (setq inchFile (getfiled "Select Inch Source Drawing" metricDir "dwg" 4))
  (if (not inchFile)
    (progn (princ "\nCancelled.") (setq *error* oldError) (princ) (exit)))

  (princ "\nOpening inch source...")
  (setq inchOpen (qc:open-inch acadObj inchFile))
  (if (not inchOpen)
    (progn (princ "\nERROR: could not open inch drawing.") (setq *error* oldError) (princ) (exit)))
  (setq inchDoc (car inchOpen) inchIsDbx (cadr inchOpen)
        *qc-active-inch-doc* inchDoc *qc-active-inch-dbx* inchIsDbx)
  (princ (if inchIsDbx " ObjectDBX OK." " visible fallback."))

  (princ "\nReading inch drawing...")
  (setq ic-res    (qc:collect inchDoc)
        inchDims  (car  ic-res)
        inchTexts (cadr ic-res)
        inchLfac  *qc-doc-lfac*)
  (princ (strcat " " (itoa (length inchDims)) " dim(s), "
                     (itoa (length inchTexts)) " text(s)."))

  (qc:close-inch inchDoc inchIsDbx)
  (setq *qc-active-inch-doc* nil *qc-active-inch-dbx* nil)
  (vla-Activate metricDoc)

  (setq dimMarks nil txtMarks nil
        dimPass 0 dimFail 0 txtPass 0 txtFail 0
        missDim 0 extraDim 0 missTxt 0 extraTxt 0)

  ;; ----------------------- DIMENSIONS -------------------------------
  ;; 3-phase pipeline, each phase only handling what the previous left over:
  ;;   Phase 1: handle match (exact 1:1 when converter preserved handles).
  ;;   Phase 2: absolute-distance match (overlaid drawings -> within 50 mm).
  ;;   Phase 3: FORCE pair (no gate) -- pairs every remaining dim 1:1, ranked
  ;;            value-correct-first then nearest.  Guarantees no EXTRA/MISSING
  ;;            unless the two drawings collected a different NUMBER of dims.
  (princ "\nMatching dimensions...")
  (setq dimRes   (qc:match-by-handle inchDims metricDims 2)
        dMatched (car   dimRes)
        dMiss    (cadr  dimRes)
        dExtra   (caddr dimRes))
  (setq dimRes   (qc:match-exact (qc:dedup-coincident dMiss)
                                 (qc:dedup-coincident dExtra)
                                 *qc-exact-tol* 'qc:dim-valok)
        dMatched (append dMatched (car dimRes))
        dMiss    (cadr  dimRes)
        dExtra   (caddr dimRes))
  (setq dimRes   (qc:match dMiss dExtra *qc-force-gate* 'qc:dim-valok)
        dMatched (append dMatched (car dimRes))
        dMiss    (cadr  dimRes)
        dExtra   (caddr dimRes))

  (foreach pr dMatched
    (setq ie   (car pr)   me (cadr pr)
          iv   (cadr ie)  mv (cadr me)
          exp  (* (abs iv) *qc-conv*)
          df   (abs (- (abs mv) exp))
          pass (<= df *qc-tol*)
          bp   (car me))
    (if pass (setq dimPass (1+ dimPass)) (setq dimFail (1+ dimFail)))
    (setq dimMarks
      (cons (list pass (if pass (qc:lbl-ok) (qc:lbl-cmp iv exp mv)) bp) dimMarks)))

  (foreach ie dMiss
    (setq iv (cadr ie) exp (* (abs iv) *qc-conv*) bp (car ie)
          dimFail (1+ dimFail) missDim (1+ missDim))
    (setq dimMarks (cons (list nil (qc:lbl-miss iv exp) bp) dimMarks)))

  (foreach me dExtra
    (setq mv (cadr me) bp (car me) dimFail (1+ dimFail) extraDim (1+ extraDim))
    (setq dimMarks (cons (list nil (qc:lbl-extra mv) bp) dimMarks)))

  (princ (strcat " done. " (itoa dimPass) " pass, " (itoa dimFail) " fail."))

  ;; ----------------------- TEXT / ATTRIB ----------------------------
  ;; Same 3-phase pipeline as dims: handle -> absolute-pos -> force pair.
  (princ "\nMatching text...")
  (setq txtRes   (qc:match-by-handle inchTexts metricTexts 3)
        tMatched (car   txtRes)
        tMiss    (cadr  txtRes)
        tExtra   (caddr txtRes))
  (setq txtRes   (qc:match-exact (qc:dedup-coincident tMiss)
                                 (qc:dedup-coincident tExtra)
                                 *qc-exact-tol* 'qc:txt-valok)
        tMatched (append tMatched (car txtRes))
        tMiss    (cadr  txtRes)
        tExtra   (caddr txtRes))
  (setq txtRes   (qc:match tMiss tExtra *qc-force-gate* 'qc:txt-valok)
        tMatched (append tMatched (car txtRes))
        tMiss    (cadr  txtRes)
        tExtra   (caddr txtRes))

  (foreach pr tMatched
    (setq ie    (car pr)   me (cadr pr)
          inums (cadr ie)  mnums (cadr me) bp (car me)
          pairs (qc:best-pairs inums mnums))
    (if (and pairs (= (length inums) (length mnums)) (= (length pairs) (length inums)))
      (progn
        (setq body nil bad nil)
        (foreach q pairs
          (setq qi (car q) qm (cadr q) qe (caddr q) qd (cadddr q))
          (if (> qd *qc-tol*) (setq bad T))
          (setq body (if body (strcat body "  |  " (qc:lbl-cmp qi qe qm))
                              (qc:lbl-cmp qi qe qm))))
        (if bad (setq txtFail (1+ txtFail)) (setq txtPass (1+ txtPass)))
        (setq txtMarks (cons (list (not bad) (if bad body (qc:lbl-ok)) bp) txtMarks)))
      (progn
        ;; count mismatch (macro dropped/added a number) -> fail
        (setq txtFail (1+ txtFail))
        (setq txtMarks
          (cons (list nil
                      (qc:lbl-cmp (car inums) (* (abs (car inums)) *qc-conv*)
                                  (if mnums (car mnums) 0.0))
                      bp)
                txtMarks)))))

  (foreach ie tMiss
    (setq inums (cadr ie) bp (car ie) txtFail (1+ txtFail) missTxt (1+ missTxt))
    (setq txtMarks
      (cons (list nil (qc:lbl-miss (car inums) (* (abs (car inums)) *qc-conv*)) bp) txtMarks)))

  (foreach me tExtra
    (setq mnums (cadr me) bp (car me) txtFail (1+ txtFail) extraTxt (1+ extraTxt))
    (setq txtMarks (cons (list nil (qc:lbl-extra (car mnums)) bp) txtMarks)))

  (princ (strcat " done. " (itoa txtPass) " pass, " (itoa txtFail) " fail."))

  ;; ----------------------- OUTPUT -----------------------------------
  (princ "\nPlacing markers...")
  (qc:clear-layers)
  (qc:ensure-layer metricDoc "MC_PASS"   3)
  (qc:ensure-layer metricDoc "MC_ERRORS" 7)  ; white for errors (user request)
  (setq balloonH (qc:balloon-height) errIdx 1)

  (foreach m (reverse dimMarks)
    (qc:place-marker (car m) (cadr m) (caddr m) balloonH)
    (if (not (car m))
      (progn (princ (strcat "\n  [" (itoa errIdx) "] DIM: " (cadr m))) (setq errIdx (1+ errIdx)))))
  (foreach m (reverse txtMarks)
    (qc:place-marker (car m) (cadr m) (caddr m) balloonH)
    (if (not (car m))
      (progn (princ (strcat "\n  [" (itoa errIdx) "] TXT: " (cadr m))) (setq errIdx (1+ errIdx)))))

  (if (zerop (+ dimFail txtFail)) (princ "\nAll checked conversions PASSED."))
  (vla-Regen metricDoc 2)

  (princ
    (strcat
      "\n--------------------------------------------\n"
      "METRIC_QC v2.10  --  handle -> absolute-pos -> FORCE 1:1 pairing\n"
      "  Inch dims=" (itoa (length inchDims)) "  Metric dims=" (itoa (length metricDims))
      "   |  Inch text=" (itoa (length inchTexts)) "  Metric text=" (itoa (length metricTexts)) "\n"
      "  Dimensions : " (itoa dimPass) " pass   " (itoa dimFail) " fail\n"
      "  Text/Attr  : " (itoa txtPass) " pass   " (itoa txtFail) " fail\n"
      "  -- dim missing / extra  : " (itoa missDim) " / " (itoa extraDim)
        "   (NONZERO => inch vs metric dim COUNT differs, not a match error)\n"
      "  -- text missing / extra : " (itoa missTxt) " / " (itoa extraTxt) "\n"
      "  Inch source : " (if inchIsDbx "ObjectDBX invisible" "visible fallback") "\n"
      "  DIMLFAC     : metric=" (qc:fmt metricLfac) "  inch=" (qc:fmt inchLfac) "\n"
      "  Ignored blocks: " *qc-ignore-blocks* "\n"
      "--------------------------------------------"))
  (if oldCmd (setvar "CMDECHO" oldCmd))
  (setq *error* oldError)
  (princ)
)
(defun c:mqc () (c:metric_check))

;;; ===================================================================
;;; MQC_DIAG  --  text-only dump (no balloons)
;;; ===================================================================
(defun c:mqc_diag
    (/ *error* oldError acadObj metricDoc metricDir inchFile inchOpen inchDoc inchIsDbx
       mc-res ic-res metricDims inchDims metricTexts inchTexts metricLfac inchLfac
       dimRes dMatched dMiss dExtra dResc txtRes tMatched tMiss tExtra tResc
       mMs mBlk mLay mSkip iMs iBlk iLay iSkip
       pr ie me iv mv exp df)
  (vl-load-com)
  (setq oldError *error*)
  (defun *error* (msg)
    (if *qc-active-inch-doc* (qc:close-inch *qc-active-inch-doc* *qc-active-inch-dbx*))
    (setq *qc-active-inch-doc* nil *qc-active-inch-dbx* nil)
    (setq *error* oldError)
    (if (and msg (not (wcmatch (strcase msg) "*CANCEL*,*QUIT*,*BREAK*")))
      (princ (strcat "\nMQC_DIAG error: " msg)))
    (princ))

  (setq acadObj   (vlax-get-acad-object)
        metricDoc (vla-get-ActiveDocument acadObj)
        metricDir (qc:dwg-folder))
  (princ "\n=== MQC_DIAG v2.10 ===")
  (princ "\nReading metric...")
  (setq mc-res (qc:collect metricDoc) metricDims (car mc-res) metricTexts (cadr mc-res)
        metricLfac *qc-doc-lfac*
        mMs *qc-dbg-msdim* mBlk *qc-dbg-blkdim* mLay *qc-dbg-laydim* mSkip *qc-dbg-skipdim*)
  (princ (strcat " " (itoa (length metricDims)) " dim(s), " (itoa (length metricTexts))
                 " text(s).  DIMLFAC=" (qc:fmt metricLfac)))

  (setq inchFile (getfiled "Select Inch Source Drawing" metricDir "dwg" 4))
  (if (not inchFile)
    (progn (princ "\nCancelled.") (setq *error* oldError) (princ) (exit)))
  (setq inchOpen (qc:open-inch acadObj inchFile))
  (if (not inchOpen)
    (progn (princ "\nERROR: could not open.") (setq *error* oldError) (princ) (exit)))
  (setq inchDoc (car inchOpen) inchIsDbx (cadr inchOpen)
        *qc-active-inch-doc* inchDoc *qc-active-inch-dbx* inchIsDbx)
  (princ "\nReading inch...")
  (setq ic-res (qc:collect inchDoc) inchDims (car ic-res) inchTexts (cadr ic-res)
        inchLfac *qc-doc-lfac*
        iMs *qc-dbg-msdim* iBlk *qc-dbg-blkdim* iLay *qc-dbg-laydim* iSkip *qc-dbg-skipdim*)
  (princ (strcat " " (itoa (length inchDims)) " dim(s), " (itoa (length inchTexts))
                 " text(s).  DIMLFAC=" (qc:fmt inchLfac)))
  (qc:close-inch inchDoc inchIsDbx)
  (setq *qc-active-inch-doc* nil *qc-active-inch-dbx* nil)
  (princ "\n>> WHERE DIMS WERE FOUND (modelspace / in-blocks / layouts / dropped):")
  (princ (strcat "\n   METRIC: ms=" (itoa mMs) "  blk=" (itoa mBlk) "  lay=" (itoa mLay) "  dropped=" (itoa mSkip)))
  (princ (strcat "\n   INCH  : ms=" (itoa iMs) "  blk=" (itoa iBlk) "  lay=" (itoa iLay) "  dropped=" (itoa iSkip)))
  (princ (strcat "\n   Inch opened via: " (if inchIsDbx "ObjectDBX" "VISIBLE FALLBACK")))

  ;; ----- DIMENSIONS: handle -> absolute-pos -> force -----
  (setq dimRes   (qc:match-by-handle inchDims metricDims 2)
        dMatched (car dimRes) dMiss (cadr dimRes) dExtra (caddr dimRes))
  (princ (strcat "\n>> dim handle-matches=" (itoa (length dMatched))
                 "  leftover inch=" (itoa (length dMiss))
                 "  metric=" (itoa (length dExtra))))
  (setq dimRes   (qc:match-exact (qc:dedup-coincident dMiss) (qc:dedup-coincident dExtra) *qc-exact-tol* 'qc:dim-valok)
        dMatched (append dMatched (car dimRes))
        dMiss    (cadr dimRes) dExtra (caddr dimRes))
  (princ (strcat "  exact-pos-matches=" (itoa (length (car dimRes)))))
  (setq dimRes   (qc:match dMiss dExtra *qc-force-gate* 'qc:dim-valok)
        dMatched (append dMatched (car dimRes))
        dMiss    (cadr dimRes) dExtra (caddr dimRes))
  (princ (strcat "  force-matches=" (itoa (length (car dimRes)))))

  (princ "\n\n=== DIMENSIONS ===")
  (princ "\n--- MATCHED ---")
  (foreach pr dMatched
    (setq ie (car pr) me (cadr pr) iv (cadr ie) mv (cadr me)
          exp (* (abs iv) *qc-conv*) df (abs (- (abs mv) exp)))
    (princ (strcat "\n  " (if (<= df *qc-tol*) "PASS  " "FAIL  ")
                   (qc:fmt iv) "\" -> " (qc:fmt mv) "mm  (exp " (qc:fmt exp)
                   "  diff " (qc:fmt df) ")")))
  (princ "\n--- MISSING inch dims (only if counts differ!) ---")
  (foreach ie dMiss
    (princ (strcat "\n  " (qc:fmt (cadr ie)) "\"  exp " (qc:fmt (* (abs (cadr ie)) *qc-conv*)) "mm")))
  (princ "\n--- EXTRA metric dims (only if counts differ!) ---")
  (foreach me dExtra
    (princ (strcat "\n  " (qc:fmt (cadr me)) "mm")))

  ;; ----- TEXT / CALLOUTS: handle -> absolute-pos -> force -----
  (setq txtRes   (qc:match-by-handle inchTexts metricTexts 3)
        tMatched (car txtRes) tMiss (cadr txtRes) tExtra (caddr txtRes))
  (princ (strcat "\n>> text handle-matches=" (itoa (length tMatched))
                 "  leftover inch=" (itoa (length tMiss))
                 "  metric=" (itoa (length tExtra))))
  (setq txtRes   (qc:match-exact (qc:dedup-coincident tMiss) (qc:dedup-coincident tExtra) *qc-exact-tol* 'qc:txt-valok)
        tMatched (append tMatched (car txtRes))
        tMiss    (cadr txtRes) tExtra (caddr txtRes))
  (princ (strcat "  exact-pos-matches=" (itoa (length (car txtRes)))))
  (setq txtRes   (qc:match tMiss tExtra *qc-force-gate* 'qc:txt-valok)
        tMatched (append tMatched (car txtRes))
        tMiss    (cadr txtRes) tExtra (caddr txtRes))
  (princ (strcat "  force-matches=" (itoa (length (car txtRes)))))

  (princ "\n\n=== TEXT / CALLOUTS ===")
  (princ "\n--- MATCHED ---")
  (foreach pr tMatched
    (setq ie (car pr) me (cadr pr))
    (princ (strcat "\n  [" (qc:fmt (car (cadr ie))) "in] <-> ["
                   (qc:fmt (car (cadr me))) "mm]   inch=\"" (caddr ie)
                   "\"  metric=\"" (caddr me) "\"")))
  (princ "\n--- MISSING (converted value found NOWHERE in metric) ---")
  (foreach ie tMiss
    (princ (strcat "\n  first=" (qc:fmt (car (cadr ie))) "in  src=\"" (caddr ie) "\"")))
  (princ "\n--- EXTRA (metric text, no inch source) ---")
  (foreach me tExtra
    (princ (strcat "\n  first=" (qc:fmt (car (cadr me))) "mm  src=\"" (caddr me) "\"")))

  (princ "\n\n=== end MQC_DIAG ===\n")
  (setq *error* oldError)
  (princ)
)

;;; ===================================================================
;;; MQC_CLEAR
;;; ===================================================================
(defun c:mqc_clear ()
  (vl-load-com)
  (qc:clear-layers)
  (vla-Regen (vla-get-ActiveDocument (vlax-get-acad-object)) 2)
  (princ "\nMC_PASS / MC_ERRORS balloons and layers removed.")
  (princ)
)
(defun c:metric_clear () (c:mqc_clear))

;;; ===================================================================
;;; MQC_TEST  --  self test
;;; ===================================================================
(defun qc:check (name ok)
  (princ (strcat "\n  " (if ok "PASS " "FAIL ") name))
  ok
)
(defun c:mqc_test (/ pass fail ok nums res m)
  (setq pass 0 fail 0)
  (princ "\nMETRIC_QC v2.10 self-test")

  (setq nums (qc:dim-numbers "%%C.03 [.76]"))
  (setq ok (and (= (length nums) 2) (equal (car nums) 0.03 1e-8)))
  (if (qc:check "diameter decimals extracted" ok) (setq pass (1+ pass)) (setq fail (1+ fail)))

  (setq nums (qc:dim-numbers "SHEET 12 REV 3"))
  (if (qc:check "title-block noise ignored" (null nums)) (setq pass (1+ pass)) (setq fail (1+ fail)))

  (setq nums (qc:dim-numbers "5/8-18 NF"))
  (if (qc:check "thread callout ignored" (null nums)) (setq pass (1+ pass)) (setq fail (1+ fail)))

  (setq nums (qc:dim-numbers "-.125"))
  (setq ok (and nums (equal (car nums) -0.125 1e-8)))
  (if (qc:check "signed decimal -.125" ok) (setq pass (1+ pass)) (setq fail (1+ fail)))

  ;; --- fillet / radius text dimensions (must be RECOGNISED) ---
  (setq nums (qc:dim-numbers "R0.06"))
  (setq ok (and (= (length nums) 1) (equal (car nums) 0.06 1e-8)))
  (if (qc:check "fillet R0.06 recognised" ok) (setq pass (1+ pass)) (setq fail (1+ fail)))

  (setq nums (qc:dim-numbers "(R6.35)"))
  (setq ok (and (= (length nums) 1) (equal (car nums) 6.35 1e-8)))
  (if (qc:check "parenthesised (R6.35) recognised" ok) (setq pass (1+ pass)) (setq fail (1+ fail)))

  (setq nums (qc:dim-numbers "R12.7"))
  (setq ok (and (= (length nums) 1) (equal (car nums) 12.7 1e-8)))
  (if (qc:check "radius R12.7 recognised" ok) (setq pass (1+ pass)) (setq fail (1+ fail)))

  (setq nums (qc:dim-numbers "(3.18)"))
  (setq ok (and (= (length nums) 1) (equal (car nums) 3.18 1e-8)))
  (if (qc:check "reference dim (3.18) recognised" ok) (setq pass (1+ pass)) (setq fail (1+ fail)))

  ;; GD&T / counterbore callout: decimals kept, angle + zero dropped
  (setq nums (qc:dim-numbers "%%C.771 +.015 -.000 X 90"))
  (setq ok (and (= (length nums) 2) (equal (car nums) 0.771 1e-8) (equal (cadr nums) 0.015 1e-8)))
  (if (qc:check "callout keeps decimals, drops angle/zero" ok) (setq pass (1+ pass)) (setq fail (1+ fail)))

  ;; one incidental word is allowed (UNDERCUT/FACE are keywords, IN is 1 prose)
  (setq nums (qc:dim-numbers ".03 UNDERCUT IN FACE"))
  (setq ok (and (= (length nums) 1) (equal (car nums) 0.03 1e-8)))
  (if (qc:check "short callout with 1 word still recognised" ok) (setq pass (1+ pass)) (setq fail (1+ fail)))

  ;; --- notes / bullets / prose (must be REJECTED) ---
  (setq nums (qc:dim-numbers "1. MATERIAL: AISI 4340 ALLOY STEEL"))
  (if (qc:check "numbered note bullet rejected" (null nums)) (setq pass (1+ pass)) (setq fail (1+ fail)))

  (setq nums (qc:dim-numbers "BREAK ALL SHARP EDGES 0.25/0.51"))
  (if (qc:check "prose note (edge break) rejected" (null nums)) (setq pass (1+ pass)) (setq fail (1+ fail)))

  (setq nums (qc:dim-numbers "5. BREAK ALL SHARP EDGES 0.25/0.51 UNLESS SPECIFIED"))
  (if (qc:check "numbered prose note rejected" (null nums)) (setq pass (1+ pass)) (setq fail (1+ fail)))

  (setq nums (qc:dim-numbers "12 X 30"))
  (if (qc:check "count x angle (integers) rejected" (null nums)) (setq pass (1+ pass)) (setq fail (1+ fail)))

  (setq nums (qc:dim-numbers "3"))
  (if (qc:check "bare bullet integer rejected" (null nums)) (setq pass (1+ pass)) (setq fail (1+ fail)))

  ;; CRITICAL: a multi-digit decimal must NOT be mistaken for a "12." bullet
  (setq nums (qc:dim-numbers "%%C12.421"))
  (setq ok (and (= (length nums) 1) (equal (car nums) 12.421 1e-8)))
  (if (qc:check "decimal 12.421 not mistaken for bullet" ok) (setq pass (1+ pass)) (setq fail (1+ fail)))

  (setq nums (qc:dim-numbers "0.625 THRU"))
  (setq ok (and (= (length nums) 1) (equal (car nums) 0.625 1e-8)))
  (if (qc:check "0.625 THRU recognised (not bullet)" ok) (setq pass (1+ pass)) (setq fail (1+ fail)))

  ;; transform matrix: rotate 90deg about origin, point (1,0) -> (0,1)
  (setq m (qc:m-from-insert (list 0.0 0.0) 1.0 1.0 (/ pi 2.0)))
  (setq res (qc:m-apply m (list 1.0 0.0)))
  (setq ok (and (equal (car res) 0.0 1e-6) (equal (cadr res) 1.0 1e-6)))
  (if (qc:check "transform matrix rotate 90" ok) (setq pass (1+ pass)) (setq fail (1+ fail)))

  ;; compose: translate then the above; point through identity*M = M
  (setq res (qc:m-apply (qc:m-compose (qc:m-identity) m) (list 1.0 0.0)))
  (setq ok (and (equal (car res) 0.0 1e-6) (equal (cadr res) 1.0 1e-6)))
  (if (qc:check "matrix compose with identity" ok) (setq pass (1+ pass)) (setq fail (1+ fail)))

  ;; POSITION MATCH: identical coordinates, value verify
  (setq res (qc:match
              (list (list (list 0.0 0.0) 2.0)    (list (list 100.0 0.0) 0.03))
              (list (list (list 0.0 0.0) 50.8)   (list (list 100.0 0.0) 0.76))
              0.20 'qc:dim-valok))
  (setq ok (= (length (car res)) 2))
  (if (qc:check "position match pairs both dims" ok) (setq pass (1+ pass)) (setq fail (1+ fail)))

  ;; missing detection: inch has a dim with no metric partner nearby
  (setq res (qc:match
              (list (list (list 0.0 0.0) 2.0) (list (list 999.0 999.0) 5.0))
              (list (list (list 0.0 0.0) 50.8))
              0.20 'qc:dim-valok))
  (setq ok (and (= (length (car res)) 1) (= (length (cadr res)) 1)))
  (if (qc:check "missing dim detected as unmatched inch" ok) (setq pass (1+ pass)) (setq fail (1+ fail)))

  ;; SHIFT TOLERANCE: metric dim nudged a little still pairs (not false-missing).
  ;; spread ~ 50 here; a 3-unit shift = 0.06 normalized < 0.20 gate.
  (setq res (qc:match
              (list (list (list 0.0 0.0) 2.0) (list (list 100.0 0.0) 1.0))
              (list (list (list 3.0 0.0) 50.8) (list (list 100.0 0.0) 25.4))
              0.20 'qc:dim-valok))
  (setq ok (and (= (length (car res)) 2) (= (length (cadr res)) 0)))
  (if (qc:check "slightly shifted dim still pairs" ok) (setq pass (1+ pass)) (setq fail (1+ fail)))

  ;; VALUE TIE-BREAKER: inch dim sits between two close metric dims that are
  ;; both inside the gate (a far anchor gives the set real spread).  The
  ;; correct-value candidate must win over the wrong-value one.
  (setq res (qc:match
              (list (list (list 202.0 0.0) 2.0))
              (list (list (list 0.0   0.0) 25.4)   ; far anchor (creates spread)
                    (list (list 200.0 0.0) 99.9)   ; wrong value, near inch
                    (list (list 204.0 0.0) 50.8))  ; correct value, near inch
              0.10 'qc:dim-valok))
  (setq ok (and (= (length (car res)) 1)
                (equal (cadr (cadr (car (car res)))) 50.8 1e-6)))
  (if (qc:check "value tie-breaker picks correct-value neighbour" ok) (setq pass (1+ pass)) (setq fail (1+ fail)))

  ;; UN-CONVERTED dim at SAME spot must still match (so it gets flagged),
  ;; not be skipped in favour of a far correct-value dim (gate tests raw
  ;; distance, so the far correct dim never enters as a candidate).
  (setq res (qc:match
              (list (list (list 0.0 0.0) 2.0))
              (list (list (list 0.0 0.0) 2.0)      ; same spot, NOT converted
                    (list (list 8.0 0.0) 50.8))    ; correct value but far
              0.10 'qc:dim-valok))
  (setq ok (and (= (length (car res)) 1)
                (equal (cadr (cadr (car (car res)))) 2.0 1e-6)))
  (if (qc:check "un-converted same-spot dim still matched (flagged)" ok) (setq pass (1+ pass)) (setq fail (1+ fail)))

  ;; value verify: 0.03 * 25.4 = 0.762 ~ 0.76 within tol
  (setq res (qc:best-pairs (list 0.03) (list 0.76)))
  (setq ok (and res (<= (cadddr (car res)) *qc-tol*)))
  (if (qc:check "0.03in -> 0.76mm passes tolerance" ok) (setq pass (1+ pass)) (setq fail (1+ fail)))

  ;; NTS catch: 703 paired with 7030 -> large diff -> fail (but paired)
  (setq res (qc:best-pairs (list 703.0) (list 7030.0)))
  (setq ok (and res (> (cadddr (car res)) *qc-tol*)))
  (if (qc:check "NTS 703->7030 flagged as fail" ok) (setq pass (1+ pass)) (setq fail (1+ fail)))

  ;; VALUE-RESCUE: inch .771 stranded by position (far metric partner) but its
  ;; converted value 19.5834 exists in an unmatched metric -> rescued, NOT missing.
  (setq res (qc:value-rescue
              (list (list (list 0.0 0.0) (list 0.771) "CBORE .771"))   ; stranded inch text
              (list (list (list 900.0 900.0) (list 19.58) "CBORE 19.58")) ; same value, far away
              'qc:txt-valok))
  (setq ok (and (= (length (car res)) 1) (= (length (cadr res)) 0)))
  (if (qc:check "value-rescue: .771 paired (not false MISSING)" ok) (setq pass (1+ pass)) (setq fail (1+ fail)))

  ;; REAL miss preserved: inch .771 but NO matching converted value anywhere.
  (setq res (qc:value-rescue
              (list (list (list 0.0 0.0) (list 0.771) "CBORE .771"))
              (list (list (list 5.0 5.0) (list 99.9) "UNRELATED 99.9"))
              'qc:txt-valok))
  (setq ok (and (= (length (car res)) 0) (= (length (cadr res)) 1)))
  (if (qc:check "value-rescue: genuine missing stays MISSING" ok) (setq pass (1+ pass)) (setq fail (1+ fail)))

  ;; COINCIDENT DEDUP: two identical dims at the same spot collapse to one;
  ;; a distinct dim elsewhere is kept.
  (setq res (qc:dedup-coincident
              (list (list (list 100.0 100.0) 2.0)
                    (list (list 100.0 100.0) 2.0)     ; exact duplicate
                    (list (list 300.0 100.0) 2.0))))  ; same value, different spot -> keep
  (setq ok (= (length res) 2))
  (if (qc:check "coincident duplicate collapsed, distinct kept" ok) (setq pass (1+ pass)) (setq fail (1+ fail)))

  ;; DEDUP must NOT merge two distinct same-value dims that are merely close.
  (setq res (qc:dedup-coincident
              (list (list (list 0.0 0.0)  5.0)
                    (list (list 50.0 0.0) 5.0)
                    (list (list 100.0 0.0) 5.0))))
  (setq ok (= (length res) 3))
  (if (qc:check "dedup keeps distinct same-value dims apart" ok) (setq pass (1+ pass)) (setq fail (1+ fail)))

  ;; HANDLE MATCH: same handle pairs regardless of position; every entity 1:1,
  ;; no EXTRA/MISSING.  Dim entry shape = (pos val handle), so handle index = 2.
  (setq res (qc:match-by-handle
              (list (list (list 0.0 0.0)   2.0 "A1")
                    (list (list 50.0 0.0)  7.13 "B2"))
              (list (list (list 999.0 9.0) 7.13 "B2")    ; far away but SAME handle
                    (list (list 0.0 0.0)   50.8 "A1"))
              2))
  (setq ok (and (= (length (car res)) 2)
                (= (length (cadr res)) 0)
                (= (length (caddr res)) 0)))
  (if (qc:check "handle match: 1:1 by handle, zero extra/missing" ok) (setq pass (1+ pass)) (setq fail (1+ fail)))

  ;; HANDLE MATCH preserves the un-converted FAIL: B2 inch 7.13 <-> metric 7.13
  ;; (handle B2) must pair so it can be flagged FAIL, not hidden.
  (setq ok nil)
  (foreach pr (car res)
    (if (and (= (cadr (car pr)) 7.13) (= (cadr (cadr pr)) 7.13)) (setq ok T)))
  (if (qc:check "handle match: un-converted dim still paired (flaggable)" ok) (setq pass (1+ pass)) (setq fail (1+ fail)))

  ;; HANDLE MATCH falls back gracefully when handles are missing (nil).
  (setq res (qc:match-by-handle
              (list (list (list 0.0 0.0) 2.0 nil))
              (list (list (list 0.0 0.0) 50.8 nil))
              2))
  (setq ok (and (= (length (car res)) 0) (= (length (cadr res)) 1) (= (length (caddr res)) 1)))
  (if (qc:check "handle match: no-handle entries fall through to position" ok) (setq pass (1+ pass)) (setq fail (1+ fail)))

  (princ (strcat "\n  " (itoa pass) " passed, " (itoa fail) " failed."))
  (princ)
)

(princ "\nMETRIC_QC.LSP v2.10 loaded.")
(princ "\n  METRIC_CHECK (or MQC) -- run QC, place balloons on metric dwg")
(princ "\n  MQC_DIAG              -- text dump: matched / missing / extra dims")
(princ "\n  MQC_CLEAR             -- erase QC balloons + layers")
(princ "\n  MQC_TEST              -- self test")
(princ)
